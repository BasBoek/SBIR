FME workspace 04_Merge_eindstatistieken_met_shape.fmw

Parameters:
- SourceDataset_ESRISHAPE = C:\Data\SBIR\data\Pilotdata_omgevormd\Omgevormde_data_pilotgebied_SBIR_MAAN_fase2.shp   # Source Esri Shapefile(s)
- DestDataset_ESRISHAPE = C:\Data\SBIR\data\Statistics\all_sats\04_yearstats_shape   # Destination Esri Shapefile Folder
- SourceDataset_CSV2_3 = C:\Data\SBIR\data\Statistics\all_sats\03_yearstats\02_all\Yearstats_all.csv   # Source CSV (Comma Separated Value) File(s)

Readers:
- ESRISHAPE_1: ESRISHAPE from $(SourceDataset_ESRISHAPE)
- CSV2_1: CSV2 from $(SourceDataset_CSV2_3)

Writers:
- ESRISHAPE_2: ESRISHAPE to $(DestDataset_ESRISHAPE)

CSV (reader CSV2_1)
    attributes: agg10 string, agg15 string, agg20 string, agg25 string, agg30 string, agg35 string, agg40 string, cutoff string, year string, band string, variable string, nr_beelden string, perceel string, mutlike string
    -> FeatureJoiner [LEFT]
Omgevormde_data_pilotgebied_SBIR_MAAN_fase2 (reader ESRISHAPE_1)
    attributes: categorie char(200), periode char(200), OBJECTID long, FUNCTIONEE char(20), NEN3610ID char(60), FYSIEKVOOR char(100), GLOBALID char(38), SHAPE_AREA number(31,15), SHAPE_LEN number(31,15)
    -> FeatureJoiner [RIGHT]
FeatureJoiner
    ATTR_CONFLICT_RES = Use Left
    GEOMETRY_HANDLING = Use Right
    JOIN_KEYS = perceel OBJECTID AUTO
    JOIN_MODE = Inner
    JOINED -> FeatureJoiner_Joined
    JOINED -> Statistieken_percelen (writer ESRISHAPE_2)
    UNJOINED_LEFT -> FeatureJoiner_UnjoinedLeft
    UNJOINED_RIGHT -> FeatureJoiner_UnjoinedRight
    <REJECTED> -> FeatureJoiner__Rejected_
FeatureJoiner_Joined: Inspector
FeatureJoiner_UnjoinedLeft: Inspector
Statistieken_percelen (writer ESRISHAPE_2)
    attributes: agg10 float, agg15 float, agg20 float, agg25 float, agg30 float, agg35 float, agg40 float, cutoff float, year char(254), band char(254), variable char(254), nr_beelden double, perceel double, mutlike double, categorie char(200), periode char(200), OBJECTID long, FUNCTIONEE char(20), NEN3610ID char(60), FYSIEKVOOR char(100), GLOBALID char(38), SHAPE_AREA number(31,15), SHAPE_LEN number(31,15)
FeatureJoiner_UnjoinedRight: Inspector
FeatureJoiner__Rejected_: Inspector
